module iproute2-cmdgen-extensions {
    yang-version 1.1;
    namespace "urn:okda:iproute2:cmdgen:extensions";
    prefix "ipr2cgen";

    organization
        "Okda networks";

    contact
        "Author: Ali Aqrabawi
        <aaqrabaw@okdanetworks.com>";

    description
        "This module provide extensions to parse yang data to ip route cmd";

    extension cmd-start {
        description
            "define at which node a new cmd start, typically used in the first list in the schema, example
            ir2cmd:cmd-start";

    }

    extension cmd-add {
        description
            "define the add cmd prefix , typically used in the first container, example
            ir2cmd:cmd-add \"ip link add\" ";
        argument "cmd";

    }
    extension cmd-delete {
        description
            "define the delete cmd prefix , typically used in the first container, example
            ir2cmd:cmd-add \"ip link delete\" ";
        argument "cmd";

    }
    extension cmd-update {
        description
            "define the update cmd prefix , typically used in the first container, example
            ir2cmd:cmd-add \"ip link set\" ";
        argument "cmd";

    }

    extension arg-name {
        description
            "iproute2 cmd generator will use the leaf name as argname when generating the cmd, to override this use
            arg-name extension";
        argument "arg-name";
    }

    extension oper-arg-name {
        description
            "iproute2 operational data extraction will use the leaf name for data lookup in iproute2 json outputs, to override this use
            oper-arg-name extension";
        argument "arg-name";
    }


    extension flag {
        description
            "iproute2 cmd generator will use the leaf name only, ususally used for flags where the leaf type will be bool,
            e.g \"ip nexthop add id 100 blackhole\" (blackhole is flag, and it's type is bool in yang)";
    }

    extension value-only{
        description
            "instruct iproute2 to drop the leaf name (key) when generating the cmd, example \"ip link add dummy0 up\"";
    }

    extension value-only-on-update{
        description
            "instruct iproute2 to drop the leaf name (key) when generating the update cmd";
    }
    extension on-update-include{
        description
            "instruct iproute2 to include the leaf(s) specified by arg-name (coma ',' separated) to be included
            on update cmd";
        argument "args-names";
    }
    extension replace-on-update{
        description
            "instruct iproute2 to get all leafs in sysrepo, compare it with the changed leaf, and apply the diff.
            typically used where iproute2 cmd require a replace for update, example tc filter, and ip nexthop group";
    }
    extension group-list-with-separator{
        description
            "instruct iproute2 to group all the list enteries together with the separator specified";
        argument "separator";
    }
    extension group-leafs-values-separator{
        description
            "instruct iproute2 to group the leafs values inside the list/container to be groupd with separator specified";
        argument "separator";
    }
    extension after-node-add-static-arg{
        description
            "instruct iproute2 to always add the static argument mentioned,
            for example for startcmd vrf always add type vrf after the leaf name";
        argument "static-arg";
    }
    extension add-static-arg{
        description
            "instruct iproute2 to add a static argument, to be used inside containers";
        argument "static-arg";
    }
    extension on-node-delete{
        description
            "when the node is deleted the provided 'arg' will be added to cmd,
            example is nomaster with removig vrf from link";
        argument "arg";
    }
}
